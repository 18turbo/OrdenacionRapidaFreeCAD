import FreeCAD

# Autor:			18Turbo
# Fecha:		14-08-2022
# Versión:		0.0.6 BETA
#	
# Funcionalidad:		Ordena grupos según sean seleccionados.
#
# Notas Importantes:	 hay que saber que los grupos sin padre tienen un orden específico en FreeCAD y no se pueden ordenar con este script
#					porque aunque se hace el proceso correcto, FreeCAD no permite la ordenación de estos de una forma simple y escapa
#					a los propósitos de este script.
#
#
# Notas de versiones:
# v.0.0.5:		Depurado para que funcione con grupos sin padre, es decir, con el documento como padre, aunque FreeCAD no lo permita. Así,
#				si en una versión superior se permite, el script no hay que modificarlo.
# v.0.0.4:		Versión Alfa funcional.
#
#
#
#
#


objetosSeleccionados = Gui.Selection.getSelection()

# Comprobando que todos tienen el mismo padre, siempre que no partan de la raíz del documento
distintoPadre = False
padre = ""

if App.ActiveDocument.getObject(objetosSeleccionados[0].Name).InList: # Esto es que tiene padre
    tienePadre = True
    for objeto in objetosSeleccionados:
        if (App.ActiveDocument.getObject(objeto.Name).InList[0].Name != padre):
            if (padre == ""):
                padre = App.ActiveDocument.getObject(objeto.Name).InList[0].Name
            else:
                distintoPadre = True
                break;
else:
    tienePadre = False
    for objeto in objetosSeleccionados:
        if (App.ActiveDocument.getObject(objeto.Name).InList):
            distintoPadre = True
    App.Console.PrintWarning("Los grupos no tienen un padre y FreeCAD no permite la ordenación en este nivel")

if not distintoPadre:
    if tienePadre:
        nombrePadre = App.ActiveDocument.getObject(objeto.Name).InList[0].Name
     
    listaNombres = []
    App.activeDocument().Tip = App.activeDocument().addObject('App::DocumentObjectGroup','GrupoAuxiliarOrdenacion')

    for objetoA in objetosSeleccionados:
        # Siempre que el objeto sea un grupo
        if (objetoA.Name.find('Group') > -1) or (objetoA.Name.find('Part') > -1):
            App.ActiveDocument.getObject(objetoA.Name).removeObject(App.ActiveDocument.getObject(objetoA.Name))
            App.ActiveDocument.getObject("GrupoAuxiliarOrdenacion").addObject(App.ActiveDocument.getObject(objetoA.Name))
            listaNombres.append(objetoA.Name) 

    for nombreObjeto in listaNombres:
        App.ActiveDocument.getObject("GrupoAuxiliarOrdenacion").removeObject(App.ActiveDocument.getObject(nombreObjeto))
        if tienePadre:
            App.ActiveDocument.getObject(nombrePadre).addObject(App.ActiveDocument.getObject(nombreObjeto))

    App.activeDocument().removeObject("GrupoAuxiliarOrdenacion")
    App.activeDocument().recompute()
else:
    App.Console.PrintWarning("Debes seleccionar Grupos con el mismo padre")
